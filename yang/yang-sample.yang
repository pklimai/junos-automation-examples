module yang-sample {
  namespace "http://yang.example.com/sample";
  prefix sample;
  organization "ACME, inc.";
  description "Sample YANG module";

  typedef ipaddr {
    type string;
  }
  
  leaf device-hostname {
    description "Device host name string";
    type string; 
    mandatory true;
  }
  
  leaf-list dns-servers {
    description "DNS servers IP or FQDN";
    type string;
  }

  container system {
    container services {
      container ssh {
        leaf enabled {
          type boolean;
        }
      }
    }
  }

  list interface-list {
    key name;
    ordered-by user;
    description "Device interfaces and their IP addrs.";
    leaf name {
      type string;
    }
    leaf address {
      type ipaddr;
    }
  }
}
